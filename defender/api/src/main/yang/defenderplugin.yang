//Contents of "defenderplugin.yang"
module defenderplugin {
    namespace "urn:opendaylight:defenderplugin";
    prefix "defenderplugin";
    organization "Northeastern University";
    contact "303193532@qq.com";
    description "identify the data struction used in the datastore,notification and RPC.";
    
    revision 2019-08-12 {
        description "identify the data struction used in the datastore,notification and RPC.";
    }
    
    // Notification消息传递IP地址和MAC地址等信息
    notification lowWaterMarkBreached {
        description
                "Indicates that the Low Water Mark has Breached.";
        leaf srcPort {
            type uint16;
        }
        leaf dstPort {
            type uint16;
        }
        leaf srcIP {
            type string;
        }
        leaf dstIP {
            type string;
        }
        leaf protocol {
            type string;
        }
        leaf srcMac {
            type string;
        }
        leaf dstMac {
            type string;
        }
    }
    // 在datastore中存储的威胁信息的结构
    container LWM {//LWM class
        list lowwatermark {//Lowwatermark class + LowatermarkKey class
            key secKey;
            leaf secKey {
                type string;
            }
            leaf nodeID {
                type string;
            }
            leaf nodeConnectorID {
                type string;
            }
            leaf srcMAC {
            	type string;
            }
            leaf dstMAC {
            	type string;
            }
            leaf srcIP {
                type string;
            }
            leaf dstIP {
                type string;
            }
            leaf protocol {
                type string;
            }
            leaf srcPort {
                type uint16;
            }
            leaf dstPort {
                type uint16;
            }
            leaf packetSize {
                type uint16;
            }
            leaf upwardTime {
                type string;
            }
            leaf downwardTime {
                type string;
            }
            config false;//get()
        }
    }
    rpc attacksFromIP{
    	input {
    		leaf SrcIP{
    			type string;
    		}
    	}
    	output {
    		uses alert;
    	}
    }
    rpc attacksToIP {
    	input {
    		leaf DstIP {
    			type string;
    		}
    	}
    	output {
    		uses alert;
    	}
    }
    rpc attacksInTime {
    	input {
    		leaf FromTime {
    			type string;
    		}
    		leaf EndTime {
    			type string;
    		}
    	}
    	output {
    		uses alert;
    	}
    }
    grouping alert {
    	list alerts {
    		leaf srcMAC {
                type string;
            }
            leaf dstMAC {
                type string;
            }
            leaf srcIP {
                type string;
            }
            leaf dstIP {
                type string;
            }
            leaf protocol {
                type string;
            }
            leaf srcPort {
                type uint16;
            }
            leaf dstPort {
                type uint16;
            }
            leaf uptime {
            	type string;
            }
            leaf downtime {
            	type string;
            }
    	}
    }
    container sample-data-lwm {
    	leaf samples-lwm {
    		type uint16;
    		mandatory true;
    	}
    	leaf lowWaterMark-lwm {
    		type uint16;
    		mandatory true;
    	}
    }
}
